# URS
This is the specifications that have been stated within the URS for th ventilator and will be assigned to the model.

## SysOP-61: Power Supply to all Sub-systems (Functional)
The power supply sub-system shall be capable of providing electrical power to all the sub-systems of the BVS
- Keywords: Power Supply

### SysOP-61-C1: Main on/off (Functional)
The system shall allow for the main on/off switch to activate standby mode, secondary function to turn the device on from standby mode.

### SysOP-61-C2: Run Time (Functional)
The system shall be able to run for a minimum of 14 days without failure and/or maintenance.

### SysOP-61-C3: Mains Power (Functional)
The system shall work from standard (South Africa 2021) 220 Volt (V) Alternating Current (AC) 50 Hertz (Hz) wall socket.

### SysOP-61-C4: Cable length (Functional)
The system shall be provided with a mains cable that is three meters long.

### SysOP-61-C5: Mains Connector (Functional)
The mains cable shall be fitted with SANS 164-4:2018 complient 15A three prong plug.

### SysOP-61-C6: Cable Prongs (Functional)
The earth pin shall be fitted to the top with a red cover.

### SysOP-61-C7: Power Failure (Functional)
In the case of power failure the system shall be able to switch from AC main power to battery operated mode.

### SysOP-61-C8: Power Resume (Functional)
The system shall switch from battery operating power to AC mains power when power is reconnected to the system.

### SysOP-61-C9: Battery Run Time (Functional)
The system shall be able to provide uninteruprted power supply from battery backup for a time period of atleast an hour when main power supply fails (NVPF3.16.1).

### SysOP-61-C10: Electrical Safety (Functional)
The systems shall be complient with Electromagnetic Complience EMC and Elevtromagnetic Interference EMI requirements as set by IEX60601, Electrical Safety1-1.

### SysOP-61-C11: Subsection Supply (Functional)
The system shall be able to privide power to the system through the control subsystem without power drop out or failure.

### SysOP-61-C12: Power Cable Clamp (Functional)
The system shall have a cable that keep the power cable connected to the system.

## SyOPS-62: Control Subsystem Primary Monitor (Functional)
The Control Sub-system shall be capable of performing all the primary monitoring and control functions of the BVS.
- Keywords: HMI Control

### SyOPS-62-C1: Presssuer over time (Functional)
Pressure ramp option that starts pressure at low level (minimum) and increases slowly over time priod to set level (User set maximum).

### SyOPS-62-C2: Spontanious Timing (Functional)
The BVS shall react to spontanious timing in reaction to the breathing of the patient.

### SyOPS-62-C3: Rebreathing (Functional)
The system shall account for 4 to 5 millimeters of CO2 rebreathing.

### SyOPS-62-C4: APAP (Functional)
The system shall allow for automatic positive airway pressure also called AutoPAP or APAP

### SyOPS-62-C5: CPAP (Functional)
The system shall be CPAP spontanious for a time (T) Pressure Assisted Control/Pressure COntrole (PAC/PC)

### SyOPS-62-C6: Inspirator and Exiratory (Functional)
The system shall allow for the programmable time functions for inspiratory and expiratory

### SyOPS-62-C7: Rise Time to Peak Flow (Functional)
The system shall be controlled ro prevent massive increase in airflow, variable rate shall be selectable.

### SyOPS-62-C8: Inspiration to Expiration (Functional)
The system shall allow the fan to operate at 30% to 50% of the peak flow rate.

### SyOPS-62-C9: Exspiration to Insiration (Functional)
The system shall allow for the flow to chang eercentage when inspiration is trggered to peak flow cycle.

### SyOPS-62-C10: Operation (Functional)
The system shall operate without fail for a minimum period of 14 days.

### SyOPS-62-C11: Low Level Alarm (Functional)
The system shall trigger an low level alarm when a low catagory failure occures while device continues function on last preset with limited capabilities.

### SyOPS-62-C12: High Levle Alarm (Functional)
The system shall trigger a high level alarm when critical failure in a main component failure, built in safty systems shall open the patient circuit to prevent obstruction.

### SyOPS-62-C13: Start-Up (Functional)
The system shall send start up function to the HMI when system is power up.

### SyOPS-62-C14: Self Test (Functional)
The system shall be capable of iniciting self testing procedure when triggered by HMI.

### SyOPS-62-C15: Information Set (Functional)
The system shall allow for the medical practitioner to set the operations

### SyOPS-62-C16: Initiate Therapy (Functional)
The system shall when triggeed by the medical practitioner inicicate the preset therapy to the patient iniciating ventilation from the Air Supply Subsystem.

### SyOPS-62-C17: Auditory Check (Functional)
The system shall detect auditory feedback via a mic or LDR.

### SyOPS-62-C18: Maintinance Mode Trigger (Functional)
The system shall be capable of entering maintainance when both button and password have been triggered.

### SyOPS-62-C19: Monitoring (Functional)
The system shall provide the HMI with monitoring infomation of the patient and system.

### SyOPS-62-C20: Shut Down Mode (Functional)
the system shall allow the operator to shutdown the unit from the HMI provided the system has not locked out shutdown either physcally or in software.

### SyOPS-62-C21: Lock out (Functional)
The system shall allow the operator to physically or in software allow for locking shutdown sequence

### SyOPS-62-C22: Shutdown Routine (Functional)
The system shall enter standby mode and apon wake up or turning on the system shal go inti Start-up mode.

### SyOPS-62-C23: Self Fuction from Software (Functional)
The system shall allow for self testing procedure when triggered by HMI.

### SyOPS-62-C24: Maintainance Self Test (Functional)
The system shall allow for self testing procedure during maintainance mode

### SyOPS-62-C25: Low Pressure Alarm (Functional)
The system shall allo for the setting of the low pressure alarm through the HMI by the operator or support equipment.

### SyOPS-62-C26: Scalable Pressure Alarm (Functional)
The system shall allow for the alarm state to be monitored and escilated if the alarm has not clear within a time period.

### SyOPS-62-C27: Alarm Trigger System Failure (Functional)
The system shall trigger high level alarm when system failure is detected.

### SyOPS-62-C28: Alarm Trigger Power Failure (Functional)
The system shall trigger low level alarm when mains power is unavaiable.

### SyOPS-62-C29: Alarm Trigger Battery Back Up Failure (Functional)
The system shall allow for High Level alarm trigger when battery backup is low on power and main power is unavailable.

### SyOPS-62-C30: Technical Alarm (Functional)
The system shall be abke to trigger a technical alarm.

### SyOPS-62-C31: Equipment Alarm (Functional)
The system shall allow for high level alarm for leak detection.

### SyOPS-62-C32: Service Alarm (Functional)
System shall trigger technical alram and show service needed on HMI 1 month before service date

### SyOPS-62-C33: Air Filter Alarm (Functional)
The system shall trigger air filter replacement technical alram and display on HMI.

### SyOPS-62-C34: Alarm Set (Functional)
The alarms shall be set to system defult within tqo minutes of startup

### SyOPS-62-C35: Silence Alarm (Functional)
The system shall allow to alarms to be silenced for a maximum of two minutes.

### SyOPS-62-C36: Patient Alarm Cancle (Functional)
The system shall allow for the alarm to be cleared once the patient has take three full breaths.

### SyOPS-62-C37: Self Test Method (Functional)
The system shall condcut the self test automatically during startup or when actioned by the user through the HMI

### SyOPS-62-C38: Instructions (Functional)
The system shall provide the procedures to do self test in the manual.

### SyOPS-62-C39: Healthcare Instructions (Functional)
The system shall provide a test method for the healthcare operator.

### SyOPS-62-C40: Internal Timer (Functional)
The system shall have an internal timer for various actons to take place.

### SyOPS-62-C41: Operator Control IPAP (Functional)
The system shall allow the operator to control the Inhalation Pressure (IPAP) from the HMI

### SyOPS-62-C42: Exhalation Pressure EPAP (Functional)
The system shall allow the operator to control the Exhalation Pressure (EPAP) through the HMI

### SyOPS-62-C43: Apnoea Period (Functional)
The system shall allow the operator to control the Apnoea Period through the HMI

### SyOPS-62-C44: Inspired Oxygen Proportion (FiO2) (Functional)
The system shall allow the operator to control the Inspired Oxygen Proportion (FiO2) through the HMI

### SyOPS-62-C45: Inspirtory Trigger Pressure (Functional)
The system shall allow the operator to control the Inspritory trigger based on pressure through the HMI

### SyOPS-62-C46: Time to Peak flow (Functional)
The system shall allow the operator to control the Time th Peak Flow through the HMI

### SyOPS-62-C47: Inspiratory Trigger Range (Functional)
The system shall allow for the inpritory trigger range from -0.5 to -15 cmH2O

### SyOPS-62-C48: Two Pressure Settings (Functional)
The system shall allow for two pressure settings being Inhalation (IPAP) and Exhalation (EPAP).

### SyOPS-62-C49: Spontanious Inhalation Patient Iniciated (Functional)
The system shall allow the operator to set the apnoea threshhold through the HMI for the alarm trigger.

### SyOPS-62-C50: Inspiration Oxygen Proportion (FiO2) (Functional)
The system shall allow the operator through the HMI to set the inspired oxygen proportion (FiO2) of the gass supplied to the patient from 21% to 100% in set incements of 10% or with a contious slider with an accuracy of 5%.

### SyOPS-62-C51: Flow Rate (Functional)
The system shall allow the operator through the HMI to set the average flow rate from 10 to 80 L/min with limit of PEEP of 4 to 20 cmH2O

### SyOPS-62-C52: Pressure Range IPAP (Functional)
The system shall allow the pressure of the IPAP to be set from 4 to 25 cmH2O

### SyOPS-62-C53: Pressure Range EPAP (PEEP) (Functional)
The system shall allow for the EPAP (PEEP) to be set on the range of 4-20 cmH2O

### SyOPS-52-C54: Pressure Range CPAP (Functional)
The system shall allow for the range to be set within 4-15 cmH2O

### SyOPS-52-C55: Data Logging Monitoring (Functional)
The system shall data log all monitored Items from the HMI keeping the information saved

### SyOPS-52-C56: Data Download (Functional)
The system shall allow for the data captured in the monitring system to be downloaded for analysis.

### SyOPS-52-C57: Technical Alarm High Priority (Functional)
The system shall allow for the high priority technical alarm to be cleared by medical personal but is to be recored then alwarm is sileced and acknowladged.

## SyOPS-63: HMI Primary control and interface (Functional)
The HMI Sub-system shall be the primary display and control interface between the medical operator and the BVS.

### SyOPS-63-C1: Trigger Sensativity cmH2O (Functional)
The system shall allow for the HMI to have a trigger sensativaty of 1-10 cmH2O in incroments of 1 cmH2O or be automatic.

### SyOPS-63-C2: Start-up Screen (Functional)
The system shall have a start up screen sequence when powered on.

### SyOPS-63-C3: Start-up Prompt Self Test (Functional)
The system shall allow the user to start the mantidory self test process on the HMI.

### SyOPS-63-C4: Start-up Predefine Setting Screen (Functional)
The system shall show a screen of predefined peramiters for the ventilator that may be edited for each setting that is elable for change by the health practitioner.

### SyOPS-63-C5: Start-up Balance System (Functional)
The system shall allow for chnges to be saved in the startup process where all changes will be shown and confirmed.

### SyOPS-63-C6: Start-up Black Box (Functional)
The system shall record all the changes that were within safe messure and monitor errors on the HMI.

### SyOPS-63-C7: Start-up Iniciate Therapy (Functional)
The system shall allow for the confirmation of iniciation of ventilating therapy for patient.

### SyOPS-63-C8: Maintenance Mode Notification and Password (Functional)
The system shall inform the operator on the HMI that the system has entered maintenance mode and qill promt for a code to enter maintenance.

### SyOPS-63-C9: Practicioners Settings (Functional)
While ventilating the setting f=of the practioner shall be locked with a key that the practioner has set.

### SyOPS-63-C10: Calibration Test (Functional)
The system shall be capable of running a calibration test (through the self test) through the HMI.

### SyOPS-63-C11: Monitoring with HMI (Functional)
The system shall allow for system monitoring through the HMI/user interface.

### SyOPS-63-C12: Monitered Parameters (Functional)
The system shall allow for selected parameters to be monitored on the HMI.

### SyOPS-63-C13: Touch Screen (Functional)
The system shall utilise a touch screen interface for the HMI.

### SyOPS-63-C14: Screen Clean (Functional)
The system shall have a touch screen that can be ceaned and disinfected without damage.

### SyOPS-63-C15: Screen Size (Functional)
The system shall utilise a screen that is 7" or 10" in diameter.

### SyOPS-63-C16: Pernament Monitors (Functional)
The system shall have the following peramitors pernamently shown on the monitor, pressure, flow and volume in a graphic scaler.

### SyOPS-63-C17: Screen Brightness (Functional)
The system shall have a brightnerss that is ledgable in direct sunlight.

### SyOPS-63-C18: Daylight mode (Functional)
The system shall allow for the chnage to nondaylight and daylight mode.

### SyOPS-63-C19: Lung Graphics (Functional)
The system shall have graphics of the lungs during ventilation.

### SyOPS-63-C20: Setting Profile (Functional)
The system shall allow for resumption onthe previous user set settings that is saved to the profile.

### SyOPS-63-C21: Failure HMI Prompt (Functional)
The system shall allow the HMI to visually shaow a failure and the type with information on the failure to appear, the HMI will also allow for the silencing prompt of the alarm (while inline of the settings of the system for the level of alarm)

### SyOPS-63-C22: Secondary Input (Functional)
The system shall allow for a secondary input through a control knob.

### SyOPS-63-C23: Control IPAP (Functional)
The system shall allow for the operator to set the perameters in the HMI of Inhalation Pressure (IPAP) while being able to control the settings.

### SyOPS-63-C24: Apnoea Period HMI (Functional)
The system shall allow for the operator to set and manage the apnoea time period.

### SyOPS-63-C25: Inspired Oxygen HMI (Functional)
The system shall allow the user to set the inspired oxygen proprtion (FiO2).

### SyOPS-63-C26: Exhalation Pressure (EPAP) (Functional)
The system shall allow for the operator to set the exhalation Pressure (EPAP).

### SyOPS-63-C27: Inspiratory Trigger Pressure Set (Functional)
The system shall allow for the operator to set the Inspiration trigger point through the HMI.

### SyOPS-63-C28: Peak Flow Time Set (Functional)
The system shall allow the operatore to set the time to peak flow through the HMI.

### SyOPS-63-C29: Insparatory Trigger Range (Functional)
The system shall allow the operatore to set the inspiratory trigger from -0.5 to -15 cmH2O through the HMI.

### SyOPS-63-C30: Pressure setting (Functional)
The system shall allow the operatore to set the IPAP and EPAP seperately through the HMI.

### SyOPS-63-C31: Apnoea Alarm Set (Functional)
The system shall allow the operatore to set the apnoea alarm limit from 10 to 40 seconds through the HMI. (NVP F.1.4)

### SyOPS-63-C32: FiO2 Percentage Set (Functional)
The system shall allow the operatore to set the inspired oxygen proportion (FiO2) from 21% to 100% with accuracy of 5% through the HMI. (NVP F.7.1)

### SyOPS-63-C33: IPAP Setting Range (Functional)
The system shall allow the operatore to set the IPAP from 4-25 cmH2O through the HMI.

### SyOPS-63-C34: EPAP Setting Range (Functional)
The system shall allow the operatore to set the EPAP from 4 to 20 cmH2O through the HMI.

### SyOPS-63-C35: CPAP Setting Range (Functional)
The system shall allow the operatore to set the CPAP from 4 to 15 cmH2O through the HMI.

### SyOPS-63-C36: Monitor IPAP and EPAP (Functional)
The system shall allow for the monitoring of IPAP and EPAP through the HMI.

### SyOPS-63-C37: Monitoring FiO2 (Functional)
The system shall allow for the monitoring of FiO2 through the HMI.

### SyOPS-63-C38: Monitoring MAP (Functional)
The system shall allow for the monitoring of Mean Airway Pressure (MAP) through the HMI.

### SyOPS-63-C39: Monitor Time to Peak Pressure (Functional)
The system shall allow for the monitoring of Time to Peak Pressure through the HMI.

### SyOPS-63-C40: Monitor Inspiration and Expiration Ratio (Functional)
The system shall allow for the monitoring of Inspiration and Exparation Ratio through the HMI.

### SyOPS-63-C41: Monitor All Variables (Functional)
The system shall allow for the monitoring of all variable that have been set through the HMI.

### SyOPS-63-C42: Monitor PEEP Pressure (Functional)
The system shall allow for the monitoring of PEEP Pressure through the HMI.

### SyOPS-63-C43: Monitoring Expiratory Flow Time and Pressure Time (Functional)
The system shall allow for the monitoring of Expiratory Flow and Pressure Time through the HMI.

### SyOPS-63-C44: Monitor Expired Breath Volume (Functional)
The system shall allow for the monitoring of Expird Breath Volume through the HMI.

### SyOPS-63-C45: Display Mode Preference (Functional)
The system shall allow the operator to choose the prefered display mode of the HMI.

### SyOPS-63-C46: Alarm Pop-ups (Functional)
The system shall display alarm pop-ups when an alarm has been triggered by the control system on the HMI

### SyOPS-63-C47: Test Manuals (Functional)
The system shall allow access to the test manuals through the HMI.

### SyOPS-63-C48: Test Accessories (Functional)
The system shall allow the operator to test the tubing and accessories from the HMI.

### SyOPS-63-C49: Test Power (Functional)
The system shall allow for the operator to switch from main power to battery to test switching capabilaties within the HMI.

### SyOPS-63-C50: Alarm Test (Functional)
The system shall allow for all alarm signals and operations to be tested through the HMI.

### SyOPS-63-C51: Circuit Test (Functional)
The system shall allow the operator to test the circuit disconnect alarm within the HMI.

### SyOPS-63-C52: Button Test (Functional)
The system shall allow for the operator to test button verification through the HMI

### SyOPS-63-C53: Alarm Visual and Audiable Test (Functional)
The system shall allow the operator to test all alarm visuals and alarm tones through the HMI.

### SyOPS-63-C54: Service Reminder and Check (Functional)
The system shall allow the operator to check when a service is due and get a reminder on month before for service through the HMI.

### SyOPS-63-C55: QR Code Manual LInk (Functional)
The system shall allow for the operator tp access the user manual via the QR Code trough the HMI.

### SyOPS-63-C56: Blower Life Time Indicator (Functional)
The system shall allow the operator to see the life time inidcator of the blower through the HMI.

## SyOPS-65: Alarm Subsystem alarm activation (Functional)
The Alarm Sub-system shall be capable of actuation of all the alarms of the BVS.

### SyOPS-65-C1: Alarm Peak Pressure (Functional)
The alarm will trigger when a pressure of 40 cmH2O

### SyOPS-65-C2: Low Catagory Failure (Functional)
The system shall trigger a low level alarm when triggered by the control system.

### SyOPS-65-C3: Alarm Critical Failure (Functional)
The system shall allow for critical alarm to be triggered by the control system.

### SyOPS-65-C4: Visual and Audio (Functional)
The system shall trigger both audiable and visual ques

### SyOPS-65-C5: Low Level Visual Alarm (Functional)
The system shall visually indicate low level alarm with an orange LED.

### SyOPS-65-C6: High Level Visual Alarm (Functional)
The system shall visually indicate high level alarm with a red LED.

### SyOPS-65-C7: Technical Visual Alarm (Functional)
The system shall visually indicate a technical alarm with a blue LED.

### SyOPS-65-C8: Alarm Access (Functional)
The system shall allow for the operator to access the perameters of the alarm.

### SyOPS-65-C9: Alarm Volume (Functional)
The system shall be locked so it can not be altered by operators

### SyOPS-65-C10: Perameters Locked (Functional)
The system shall lock all peramiters of the alarm other than trigger points.

### SyOPS-65-C11: Alarm Descibel Scale (Functional)
The system shall be capable of scalable in decible level or tone when not addressed for two minutes.

### SyOPS-65-C12: Number of Alarms (Functional)
The system shall be limited to three catagories of alarms (technical low level and high level)

### SyOPS-65-C13: Alarm Limits Violated (Functional)
The system shall trigger the alarm if the limits have been violated

### SyOPS-65-C14: Breathing Alarm (Functional)
The system shall trigger a high level alarm when the patient shows no breathing effort (NVP F.13.1).

### SyOPS-65-C15: High Low Pressure (Functional)
The system shall trigger the high level alarm if the pressure of the system is outside of the preset high or low range.

### SyOPS-65-C16: Breathing Circuit (Functional)
The system shall trigger a high level alarm when the patient breathing circuit is abruptly disconnected.

### SyOPS-65-C17: Oxygen Supply Failure (Functional)
The system shall trigger a high level alarm when an oxygen supply failure is detected.

### SyOPS-65-C18: Air Supply Failure (Functional)
The system shall trigger a high level alarm when the air supply has failed.

### SyOPS-65-C19: Apnoea Alarm (Functional)
The system shall trigger a high level alarm when apnoea is detected by the control system.

### SyOPS-65-C20: High Insieration Rate (Functional)
The system shall trigger a low level alarm when high breathing rate is measured.

### SyOPS-65-C21: High Level Alarm Clear (Functional)
The system shall only allow for high level alarms to be clear only when issue has been resolved.

### SyOPS-65-C22: Technical Type of Alarm (Functional)
The system shall trigger a techniical alarm when battery is running low or service is needed.

### SyOPS-65-C23: Low Level Alarm Type (Functional)
The system shall trigger a low level trigger when minor peramiters set by the operator are violated.

### SyOPS-65-C24: High Level Alarm Type (Functional)
The system shall trigger the high level alarm when a system debiliting error ocures.

## SyOPS-66: RMT Subsystem Provide information (Functional)
The Remote monitoring Sub-system shall be capable of providing BVS information to a remote terminal.

### SyOPS-66-C1: Remote Monitor (Functional)
The system shall allow for the system to monitored in a location that is convinient for the operator.

### SyOPS-66-C2: Mirror (Functional)
The system shall mirror the monitoring screen of the screen on the ventilator.

## SyOPS-67: Air Supply Subsystem Air mix (Functional)
The Air Supply Sub-system shall be capable of selecting mixing and regulating the ventilator air stream.

### SyOPS-67-C1: Constant Air Supply (Functional)
The system shall supply air on its own without need of the air supply unit being connected.

### SyOPS-67-C2: Medical Air (Functional)
The system shall have an internal blower that can contiue the operation when medical air is not supplied or run without the need of medical air.

### SyOPS-67-C3: Air Mix (Functional)
The system shal be capable of micing oxygen into the ambient airflow.

### SyOPS-67-C4: Blower Peak Flow (Functional)
The system shall be capable of delievering a maximum of 160L/min of mixed air with compensation for leakage.

### SyOPS-67-C5: Pressure (Functional)
The system shall be capable of delievering the flow rate at the set pressure from the control system.

### SyOPS-67-C6: Normal Use Range (Functional)
The normal use range of the system shall be capable of operating without failure betweeen 80 to 100L/min.

### SyOPS-67-C7: Noise (Functional)
The system shall operate between 80 to 100L/min with a noise level of 35dBA (or lower) at a distance of one meter.

### SyOPS-67-C8: Flow Rate (Functional)
The system shall be capable of providing a flow rate of 80 to 260 L/min to compensate for air leakages.

### SyOPS-67-C9: Turbine high flow rate (Functional)
The system shall have a turbine that does not limit at 260L/min to avoid wearout.

### SyOPS-67-C10: Flow Genarator (Functional)
The system shall utilise a software signal flow genarator to manipulate air flow.

### SyOPS-67-C11: No Medical Air (Functional)
The system shall function in the absence of medical air.

### SyOPS-67-C12: Dual System (Functional)
The system shall be able to supply air and gas.

### SyOPS-67-C13: Ambient Air Inlet (Functional)
The system shall filter the ambient air inlet such no impuraties can enter the patients air ways.

### SyOPS-67-C14: Oxygen Addition (Functional)
The system shall add oxygen within the air suply unit.

## SyOPS-68: Patient Subsystem Provide BiPAP air (Functional)
The Patient Interface Sub-system shall be capable of providing BiPAP air to the patient.

### SyOPS-68-C1: Oxygen Nasal Inlet (Functional)
The system shall allow for the patient mask for nasal oxygen inlet.

### SyOPS-68-C2: Pressure Suplied (Functional)
The system patient interface shall allow for pressure of 200-500Kpa (NVP 1.3)

### SyOPS-68-C3: Hose (Functional)
The hose from the system shall have a three meter long hose that can withstand the pressure.

### SyOPS-68-C4: Oxygen Outlet (Functional)
The system shall be able to connect to the standard (South African 2021) wall outlet cylinder.

### SyOPS-68-C5: Air Switch (Functional)
The system shall be capable of switching from hosital supplied medical air and turbine supplied ambient air.

### SyOPS-68-C6: Gas Connectors and Hoses (Functional)
The system shall abide by ISO7396-1:2016 medical gas pipeline systems-Part 1: Pipeline systems for compressed medical gases and vacuum.

### SyOPS-68-C7: Outlet and Probes (Functional)
The system shall abide to SANS 1409:2014 Outlet sockets and probes for medical (gas and vacuum) services used in hospitals,

### SyOPS-68-C8: Cones and Sockets (Functional)
The system shall abide by ISO: 5356-1:2015 Anaesthetic and respository equipment - Conical connectors- Part 1: Cones and sockets

### SyOPS-68-C9: Breathing Gas Pathway (Functional)
the system shall allow for the assembling of the breathing gas pathway, including connection of the detachable parts of the gas pathway to the air supply subsystem

### SyOPS-68-C10: Humidifier Attach (Functional)
The system shall have the capability of connecting of a humidifier to the patient interface as an external system.

### SyOPS-68-C11: Mask Size (Functional)
The system shall make use of a full face mask or half face mask.

### SyOPS-68-C12: Mask Comfert (Functional)
The system shall have a mask that mitigates chances of sores when resting on the patients face.

### SyOPS-68-C13: Humidifier (Functional)
The system shall when humidifying via external meas humidify by the inspired gas actively (servo controlled heated humidifier) or heat and moisture exchange filyer (HMEF) at the patient interface (NVP F.8.1).

### SyOPS-68-C14: External Humidifier (Functional)
The system shall allow for the addition of a humidifier on the patient interfce and not an internal humidifier.

### SyOPS-68-C15: Bacteria Filter (Functional)
The system shall have a bacterial filter in the patient interface.

### SyOPS-68-C16: Nasal Mask (Functional)
The system shall be provided with a nasal mask for adult abd paediatric with relavaent tubing.

### SyOPS-68-C17: Oral Mask (Functional)
The system shall provide a oral mask for adult and paediatric.

### SyOPS-68-C18: Single Use (Functional)
The instraments that come into contact with the patient will be treated as single use consumables and other elements shall be able to withstand harsh disinfectant chemicals.

### SyOPS-68-C19: Harmful Consumable (Functional)
The system shall avoid or account for consumables that may cause additional damage to the patient.

### SyOPS-68-C20: Manditory filter (Functional)
The system shall have a manditory bacteria filter with reusable accessories.

### SyOPS-68-C21: Nasal Mask Clean (Functional)
The system shall utilise adult and paediatric nasal mask and tubing that can be cleaned with high level disinfectants and sterilization.

### SyOPS-68-C22: Oral Mask Clean (Functional)
The system shall utilise adult and paediatric oral mask and tubing that can be cleaned with high level disinfectants and sterilization.

### SyOPS-68-C23: Helmet Clean (Functional)
The system shall utilise adult and paediatric helmet and tubing that can be cleaned with high level disinfectants and sterilization.

### SyOPS-68-C24: Connectors (Functional)
The system shall allow for connectors for air and oxygen outlets, asaptable for most connectors including barb, NF, DISS and NIST.

### SyOPS-68-C25: Hose Clamp (Functional)
The system shall include a hose clamp that keep hose secured to the system.
